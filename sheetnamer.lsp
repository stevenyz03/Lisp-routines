(defun c:sheetnamer ( / sheetnameBase1 sheetnameBase2 layout lname sname sEnt seData newsEdata) 

	(setq sheetnameBase1 (list 31.5 0.75))
  	(setq sheetnameBase2 (list 33.75 0))
	(setvar "ctab" "M-1.01")
	(command "_.PSPACE")
 	(foreach layout (layoutlist)
  		(setvar "ctab" layout)
		(setq lname (getvar "ctab"))
		(setq sname (ssget "w" sheetnameBase1 sheetnameBase2))
  		(setq sEnt (ssname sname 0))
		(setq seData (entget sEnt))
		(setq newsEdata (subst (cons 1 lname) (assoc 1 seData) seData))
		(entmod newsEdata)
  	)
)
