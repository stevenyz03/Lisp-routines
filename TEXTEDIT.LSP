(defun c:textedit1 ( / nameBase1 nameBase2 sheetNum sheetcount numString sheetString sheetcoord1 sheetcoord2 sheetcount sheetName textent eData newEdata fsheetNum fsheetcount fnumString fsheetString fsheetcoord1 fsheetcoord2 fsheetcount fsheetName ftextent feData fnewEdata psheetNum psheetcount pnumString psheetString psheetcoord1 psheetcoord2 psheetcount psheetName ptextent peData pnewEdata hsheetNum hsheetcount hnumString hsheetString hsheetcoord1 hsheetcoord2 hsheetcount hsheetName htextent heData hnewEdata) 
	;(setq oldsnap (getvar "osmode"))
	;(setvar "osmode" 0)
  
	(setq 
        nameBase1 (list -292 -1167)
        nameBase2 (list 293 -1272)  
	)
	
  	(setq sheetNum 6)
	(setq sheetcount 0)
	(while (< sheetcount sheetNum)	
			(setq numString (itoa sheetcount))
			(setq sheetString (strcat "SHEET M-" numString ".01")) 
			(setq sheetcoord1 (list (+ (* sheetcount 3500) (nth 0 nameBase1)) -1167))
			(setq sheetcoord2 (list (+ (* sheetcount 3500) (nth 0 nameBase2)) -1272))
			(setq sheetcount (1+ sheetcount))
			(setq sheetName (ssget "w" sheetcoord1 sheetcoord2))
  			(setq textent (ssname sheetName 0))
			(setq eData (entget textent))
			(setq newEdata (subst (cons 1 sheetString) (assoc 1 eData) eData))
			(entmod newEdata)
	)

	(setq fsheetNum fCopynum)
	(setq fsheetcount 1)
	(while (< fsheetcount fsheetNum)
    		(setq fnumString (itoa (+ fsheetcount 1)))
			(setq fsheetString (strcat "SHEET M-1.0" fnumString)) 
			(setq fsheetcoord1 (list 3208 (+ (* fsheetcount 2700) (nth 1 nameBase1))))
			(setq fsheetcoord2 (list 3793 (+ (* fsheetcount 2700) (nth 1 nameBase2))))
			(setq fsheetcount (1+ fsheetcount))
			(setq fsheetName (ssget "w" fsheetcoord1 fsheetcoord2))
  			(setq ftextent (ssname fsheetName 0))
			(setq feData (entget ftextent))
			(setq fnewEdata (subst (cons 1 fsheetString) (assoc 1 feData) feData))
			(entmod fnewEdata)
    
	)
	
	(setq psheetNum pCopynum)
	(setq psheetcount 1)
	(while (< psheetcount psheetNum)
    		(setq pnumString (itoa (+ psheetcount 1)))
			(setq psheetString (strcat "SHEET M-2.0" pnumString)) 
			(setq psheetcoord1 (list 6708 (+ (* psheetcount 2700) (nth 1 nameBase1))))
			(setq psheetcoord2 (list 7293 (+ (* psheetcount 2700) (nth 1 nameBase2))))
			(setq psheetcount (1+ psheetcount))
			(setq psheetName (ssget "w" psheetcoord1 psheetcoord2))
  			(setq ptextent (ssname psheetName 0))
			(setq peData (entget ptextent))
			(setq pnewEdata (subst (cons 1 psheetString) (assoc 1 peData) peData))
			(entmod pnewEdata)
    
	)
  
	(setq hsheetNum hCopynum)
	(setq hsheetcount 1)
	(while (< hsheetcount hsheetNum)
    		(setq hnumString (itoa (+ hsheetcount 1)))
			(setq hsheetString (strcat "SHEET M-3.0" hnumString)) 
			(setq hsheetcoord1 (list 10208 (+ (* hsheetcount 2700) (nth 1 nameBase1))))
			(setq hsheetcoord2 (list 10793 (+ (* hsheetcount 2700) (nth 1 nameBase2))))
			(setq hsheetcount (1+ hsheetcount))
			(setq hsheetName (ssget "w" hsheetcoord1 hsheetcoord2))
  			(setq htextent (ssname hsheetName 0))
			(setq heData (entget htextent))
			(setq hnewEdata (subst (cons 1 hsheetString) (assoc 1 heData) heData))
			(entmod hnewEdata)
    
	)
	;(setvar "osmode" oldsnap)
  	(princ)

)
